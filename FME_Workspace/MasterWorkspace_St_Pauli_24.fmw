FME workspace MasterWorkspace_St_Pauli_24.fmw

Parameters:
- SourceDataset_CITYGML = C:\Users\twendt\OneDrive - virtualcitysystems GmbH\UNIGS\4. Semester\Masterarbeit\Hamburg St.Pauli\Dateien\CityGML_St_Pauli_24.gml   # Source CityGML File(s)
- HEIGHT_XPlan = 3   # StoreyHeightXPlan
- HEIGHT_CityGML = 3   # StoreyHeightCityGML
- SourceDataset_GML = C:\Users\twendt\OneDrive - virtualcitysystems GmbH\UNIGS\4. Semester\Masterarbeit\Hamburg St.Pauli\Dateien\XPlanGML_St_Pauli_24.gml   # Source Geography Markup Language (GML) File(s)
- SourceDataset_GEOJSON = C:\Users\twendt\OneDrive - virtualcitysystems GmbH\UNIGS\4. Semester\Masterarbeit\Hamburg St.Pauli\Dateien\Flurstücke_St_Pauli24.json   # Source GeoJSON File or URL
- MINAREA = 10   # Minimum Bau Area
- DestDataset_XLSXW = $(FME_MF_DIR)OutputFiles\Potential_List_Excel.xlsx   # Destination Microsoft Excel File
- DestDataset_GLTF = $(FME_MF_DIR)OutputFiles   # Destination glTF Folder

Readers:
- CITYGML_1: CITYGML from $(SourceDataset_CITYGML)
- GML_1: GML from $(SourceDataset_GML)
- GEOJSON_1: GEOJSON from $(SourceDataset_GEOJSON)

Writers:
- XLSXW_1: XLSXW to $(DestDataset_XLSXW)
- GLTF_1: GLTF to $(DestDataset_GLTF)

Aggregator_4
    ACCUM_ATTRS_NAME = Drop Incoming Attributes
    AGGREGATE_TYPE = Homogeneous Collection (If Possible)
    MODE = Geometry - Assemble One Level
    SEP = ,
    AGGREGATE -> CityGML_XPlanVergleich (writer GLTF_1)

Bookmark: XPlanGML Input Feature
BP_UeberbaubareGrundstuecksFlaeche (reader GML_1)
    attributes: uuid xml_buffer, text xml_buffer, rechtsstand xml_char(4), gesetzlicheGrundlage xml_buffer, gesetzlicheGrundlage.codeSpace xml_buffer, gliederung1 xml_buffer, gliederung2 xml_buffer, ebene xml_int32, hatGenerAttribut{}.XP_DatumAttribut.name xml_buffer, hatGenerAttribut{}.XP_DatumAttribut.wert xml_date, hatGenerAttribut{}.XP_DoubleAttribut.name xml_buffer, hatGenerAttribut{}.XP_DoubleAttribut.wert xml_real64, hatGenerAttribut{}.XP_IntegerAttribut.name xml_buffer, hatGenerAttribut{}.XP_IntegerAttribut.wert xml_int32, hatGenerAttribut{}.XP_StringAttribut.name xml_buffer, hatGenerAttribut{}.XP_StringAttribut.wert xml_buffer, hatGenerAttribut{}.XP_URLAttribut.name xml_buffer, hatGenerAttribut{}.XP_URLAttribut.wert xml_buffer, hatGenerAttribut{}.XP_GenerAttribut.name xml_buffer, hoehenangabe{}.XP_Hoehenangabe.abweichenderHoehenbezug xml_buffer, hoehenangabe{}.XP_Hoehenangabe.hoehenbezug xml_char(4), hoehenangabe{}.XP_Hoehenangabe.abweichenderBezugspunkt xml_buffer, hoehenangabe{}.XP_Hoehenangabe.bezugspunkt xml_char(4), hoehenangabe{}.XP_Hoehenangabe.hMin xml_real64, hoehenangabe{}.XP_Hoehenangabe.hMin.uom xml_buffer, hoehenangabe{}.XP_Hoehenangabe.hMax xml_real64, hoehenangabe{}.XP_Hoehenangabe.hMax.uom xml_buffer, hoehenangabe{}.XP_Hoehenangabe.hZwingend xml_real64, hoehenangabe{}.XP_Hoehenangabe.hZwingend.uom xml_buffer, hoehenangabe{}.XP_Hoehenangabe.h xml_real64,
      hoehenangabe{}.XP_Hoehenangabe.h.uom xml_buffer, hoehenangabe{}.XP_Hoehenangabe._GenericApplicationPropertyOfXP_Hoehenangabe{} xml_xml, externeReferenz{}.XP_SpezExterneReferenz.georefURL xml_buffer, externeReferenz{}.XP_SpezExterneReferenz.georefMimeType xml_buffer, externeReferenz{}.XP_SpezExterneReferenz.georefMimeType.codeSpace xml_buffer, externeReferenz{}.XP_SpezExterneReferenz.art xml_char(18), externeReferenz{}.XP_SpezExterneReferenz.informationssystemURL xml_buffer, externeReferenz{}.XP_SpezExterneReferenz.referenzName xml_buffer, externeReferenz{}.XP_SpezExterneReferenz.referenzURL xml_buffer, externeReferenz{}.XP_SpezExterneReferenz.referenzMimeType xml_buffer, externeReferenz{}.XP_SpezExterneReferenz.referenzMimeType.codeSpace xml_buffer, externeReferenz{}.XP_SpezExterneReferenz.beschreibung xml_buffer, externeReferenz{}.XP_SpezExterneReferenz.datum xml_date, externeReferenz{}.XP_SpezExterneReferenz._GenericApplicationPropertyOfXP_ExterneReferenz{} xml_xml, externeReferenz{}.XP_SpezExterneReferenz.typ xml_char(4), externeReferenz{}.XP_SpezExterneReferenz._GenericApplicationPropertyOfXP_SpezExterneReferenz{} xml_xml, gehoertZuBereich.nilReason xml_buffer, gehoertZuBereich.gml_remoteSchema xml_buffer, gehoertZuBereich.xlink_href xml_buffer, gehoertZuBereich.xlink_role xml_buffer, gehoertZuBereich.xlink_title xml_buffer, wirdDargestelltDurch{}.nilReason xml_buffer, wirdDargestelltDurch{}.gml_remoteSchema xml_buffer, wirdDargestelltDurch{}.xlink_href xml_buffer, wirdDargestelltDurch{}.xlink_role xml_buffer, wirdDargestelltDurch{}.xlink_title xml_buffer, refBegruendungInhalt{}.nilReason xml_buffer, refBegruendungInhalt{}.gml_remoteSchema xml_buffer, refBegruendungInhalt{}.xlink_href xml_buffer, refBegruendungInhalt{}.xlink_role xml_buffer,
      refBegruendungInhalt{}.xlink_title xml_buffer, startBedingung.XP_WirksamkeitBedingung.bedingung xml_buffer, startBedingung.XP_WirksamkeitBedingung.datumAbsolut xml_date, startBedingung.XP_WirksamkeitBedingung.datumRelativ xml_buffer, startBedingung.XP_WirksamkeitBedingung._GenericApplicationPropertyOfXP_WirksamkeitBedingung{} xml_xml, endeBedingung.XP_WirksamkeitBedingung.bedingung xml_buffer, endeBedingung.XP_WirksamkeitBedingung.datumAbsolut xml_date, endeBedingung.XP_WirksamkeitBedingung.datumRelativ xml_buffer, endeBedingung.XP_WirksamkeitBedingung._GenericApplicationPropertyOfXP_WirksamkeitBedingung{} xml_xml, aufschrift xml_buffer, _GenericApplicationPropertyOfXP_Objekt{} xml_xml, rechtscharakter xml_char(4), refTextInhalt{}.nilReason xml_buffer, refTextInhalt{}.gml_remoteSchema xml_buffer, refTextInhalt{}.xlink_href xml_buffer, refTextInhalt{}.xlink_role xml_buffer, refTextInhalt{}.xlink_title xml_buffer, wirdAusgeglichenDurchFlaeche{}.nilReason xml_buffer, wirdAusgeglichenDurchFlaeche{}.gml_remoteSchema xml_buffer, wirdAusgeglichenDurchFlaeche{}.xlink_href xml_buffer, wirdAusgeglichenDurchFlaeche{}.xlink_role xml_buffer, wirdAusgeglichenDurchFlaeche{}.xlink_title xml_buffer, wirdAusgeglichenDurchABE{}.nilReason xml_buffer, wirdAusgeglichenDurchABE{}.gml_remoteSchema xml_buffer, wirdAusgeglichenDurchABE{}.xlink_href xml_buffer, wirdAusgeglichenDurchABE{}.xlink_role xml_buffer, wirdAusgeglichenDurchABE{}.xlink_title xml_buffer, wirdAusgeglichenDurchSPEMassnahme{}.nilReason xml_buffer, wirdAusgeglichenDurchSPEMassnahme{}.gml_remoteSchema xml_buffer, wirdAusgeglichenDurchSPEMassnahme{}.xlink_href xml_buffer,
      wirdAusgeglichenDurchSPEMassnahme{}.xlink_role xml_buffer, wirdAusgeglichenDurchSPEMassnahme{}.xlink_title xml_buffer, wirdAusgeglichenDurchSPEFlaeche{}.nilReason xml_buffer, wirdAusgeglichenDurchSPEFlaeche{}.gml_remoteSchema xml_buffer, wirdAusgeglichenDurchSPEFlaeche{}.xlink_href xml_buffer, wirdAusgeglichenDurchSPEFlaeche{}.xlink_role xml_buffer, wirdAusgeglichenDurchSPEFlaeche{}.xlink_title xml_buffer, wirdAusgeglichenDurchMassnahme{}.nilReason xml_buffer, wirdAusgeglichenDurchMassnahme{}.gml_remoteSchema xml_buffer, wirdAusgeglichenDurchMassnahme{}.xlink_href xml_buffer, wirdAusgeglichenDurchMassnahme{}.xlink_role xml_buffer, wirdAusgeglichenDurchMassnahme{}.xlink_title xml_buffer, _GenericApplicationPropertyOfBP_Objekt{} xml_xml, position xml_geometry, flaechenschluss xml_boolean, _GenericApplicationPropertyOfBP_Flaechenobjekt{} xml_xml, _GenericApplicationPropertyOfBP_Ueberlagerungsobjekt{} xml_xml, dachgestaltung{}.BP_Dachgestaltung.DNmin xml_real64, dachgestaltung{}.BP_Dachgestaltung.DNmin.uom xml_buffer, dachgestaltung{}.BP_Dachgestaltung.DNmax xml_real64, dachgestaltung{}.BP_Dachgestaltung.DNmax.uom xml_buffer, dachgestaltung{}.BP_Dachgestaltung.DN xml_real64, dachgestaltung{}.BP_Dachgestaltung.DN.uom xml_buffer, dachgestaltung{}.BP_Dachgestaltung.DNzwingend xml_real64, dachgestaltung{}.BP_Dachgestaltung.DNzwingend.uom xml_buffer, dachgestaltung{}.BP_Dachgestaltung.dachform xml_char(4), dachgestaltung{}.BP_Dachgestaltung.detaillierteDachform xml_buffer, dachgestaltung{}.BP_Dachgestaltung.detaillierteDachform.codeSpace xml_buffer, dachgestaltung{}.BP_Dachgestaltung._GenericApplicationPropertyOfBP_Dachgestaltung{} xml_xml, DNmin xml_real64,
      DNmin.uom xml_buffer, DNmax xml_real64, DNmax.uom xml_buffer, DN xml_real64, DN.uom xml_buffer, DNZwingend xml_real64, DNZwingend.uom xml_buffer, FR xml_real64, FR.uom xml_buffer, dachform{} xml_char(4), detaillierteDachform{} xml_buffer, detaillierteDachform{}.codeSpace xml_buffer, MaxZahlWohnungen xml_int32, Fmin xml_real64, Fmin.uom xml_buffer, Fmax xml_real64, Fmax.uom xml_buffer, Bmin xml_real64, Bmin.uom xml_buffer, Bmax xml_real64, Bmax.uom xml_buffer, Tmin xml_real64, Tmin.uom xml_buffer, Tmax xml_real64, Tmax.uom xml_buffer, GFZmin xml_real64, GFZmax xml_real64, GFZ xml_real64, GFZ_Ausn xml_real64, GFmin xml_real64,
      GFmin.uom xml_buffer, GFmax xml_real64, GFmax.uom xml_buffer, GF xml_real64, GF.uom xml_buffer, GF_Ausn xml_real64, GF_Ausn.uom xml_buffer, BMZ xml_real64, BMZ_Ausn xml_real64, BM xml_real64, BM.uom xml_buffer, BM_Ausn xml_real64, BM_Ausn.uom xml_buffer, GRZmin xml_real64, GRZmax xml_real64, GRZ xml_real64, GRZ_Ausn xml_real64, GRmin xml_real64, GRmin.uom xml_buffer, GRmax xml_real64, GRmax.uom xml_buffer, GR xml_real64, GR.uom xml_buffer, GR_Ausn xml_real64, GR_Ausn.uom xml_buffer, Zmin xml_int32, Zmax xml_int32, Zzwingend xml_int32, Z xml_int32, Z_Ausn xml_int32,
      Z_Staffel xml_int32, Z_Dach xml_int32, ZUmin xml_int32, ZUmax xml_int32, ZUzwingend xml_int32, ZU xml_int32, ZU_Ausn xml_int32, wohnnutzungEGStrasse xml_char(4), ZWohn xml_int32, GFAntWohnen xml_real64, GFAntWohnen.uom xml_buffer, GFWohnen xml_real64, GFWohnen.uom xml_buffer, GFAntGewerbe xml_real64, GFAntGewerbe.uom xml_buffer, GFGewerbe xml_real64, GFGewerbe.uom xml_buffer, bauweise xml_char(4), abweichendeBauweise xml_buffer, abweichendeBauweise.codeSpace xml_buffer, vertikaleDifferenzierung xml_boolean, bebauungsArt xml_char(4), bebauungVordereGrenze xml_char(4), bebauungRueckwaertigeGrenze xml_char(4), bebauungSeitlicheGrenze xml_char(4), refGebaeudequerschnitt{}.XP_SpezExterneReferenz.georefURL xml_buffer, refGebaeudequerschnitt{}.XP_SpezExterneReferenz.georefMimeType xml_buffer, refGebaeudequerschnitt{}.XP_SpezExterneReferenz.georefMimeType.codeSpace xml_buffer, refGebaeudequerschnitt{}.XP_SpezExterneReferenz.art xml_char(18), refGebaeudequerschnitt{}.XP_SpezExterneReferenz.informationssystemURL xml_buffer,
      refGebaeudequerschnitt{}.XP_SpezExterneReferenz.referenzName xml_buffer, refGebaeudequerschnitt{}.XP_SpezExterneReferenz.referenzURL xml_buffer, refGebaeudequerschnitt{}.XP_SpezExterneReferenz.referenzMimeType xml_buffer, refGebaeudequerschnitt{}.XP_SpezExterneReferenz.referenzMimeType.codeSpace xml_buffer, refGebaeudequerschnitt{}.XP_SpezExterneReferenz.beschreibung xml_buffer, refGebaeudequerschnitt{}.XP_SpezExterneReferenz.datum xml_date, refGebaeudequerschnitt{}.XP_SpezExterneReferenz._GenericApplicationPropertyOfXP_ExterneReferenz{} xml_xml, refGebaeudequerschnitt{}.XP_SpezExterneReferenz.typ xml_char(4), refGebaeudequerschnitt{}.XP_SpezExterneReferenz._GenericApplicationPropertyOfXP_SpezExterneReferenz{} xml_xml, refGebaeudequerschnitt{}.XP_ExterneReferenz.georefURL xml_buffer, refGebaeudequerschnitt{}.XP_ExterneReferenz.georefMimeType xml_buffer, refGebaeudequerschnitt{}.XP_ExterneReferenz.georefMimeType.codeSpace xml_buffer, refGebaeudequerschnitt{}.XP_ExterneReferenz.art xml_char(18), refGebaeudequerschnitt{}.XP_ExterneReferenz.informationssystemURL xml_buffer, refGebaeudequerschnitt{}.XP_ExterneReferenz.referenzName xml_buffer, refGebaeudequerschnitt{}.XP_ExterneReferenz.referenzURL xml_buffer, refGebaeudequerschnitt{}.XP_ExterneReferenz.referenzMimeType xml_buffer, refGebaeudequerschnitt{}.XP_ExterneReferenz.referenzMimeType.codeSpace xml_buffer, refGebaeudequerschnitt{}.XP_ExterneReferenz.beschreibung xml_buffer, refGebaeudequerschnitt{}.XP_ExterneReferenz.datum xml_date, refGebaeudequerschnitt{}.XP_ExterneReferenz._GenericApplicationPropertyOfXP_ExterneReferenz{} xml_xml, baugrenze{}.nilReason xml_buffer, baugrenze{}.gml_remoteSchema xml_buffer, baugrenze{}.xlink_href xml_buffer, baugrenze{}.xlink_role xml_buffer, baugrenze{}.xlink_title xml_buffer, baulinie{}.nilReason xml_buffer, baulinie{}.gml_remoteSchema xml_buffer, baulinie{}.xlink_href xml_buffer, baulinie{}.xlink_role xml_buffer,
      baulinie{}.xlink_title xml_buffer, geschossMin xml_int32, geschossMax xml_int32, _GenericApplicationPropertyOfBP_UeberbaubareGrundstuecksFlaeche{} xml_xml
    -> AreaOnAreaOverlayer_2 [AREA]
BP_BaugebietsTeilFlaeche (reader GML_1)
    attributes: uuid xml_buffer, text xml_buffer, rechtsstand xml_char(4), gesetzlicheGrundlage xml_buffer, gesetzlicheGrundlage.codeSpace xml_buffer, gliederung1 xml_buffer, gliederung2 xml_buffer, ebene xml_int32, hatGenerAttribut{}.XP_DatumAttribut.name xml_buffer, hatGenerAttribut{}.XP_DatumAttribut.wert xml_date, hatGenerAttribut{}.XP_DoubleAttribut.name xml_buffer, hatGenerAttribut{}.XP_DoubleAttribut.wert xml_real64, hatGenerAttribut{}.XP_IntegerAttribut.name xml_buffer, hatGenerAttribut{}.XP_IntegerAttribut.wert xml_int32, hatGenerAttribut{}.XP_StringAttribut.name xml_buffer, hatGenerAttribut{}.XP_StringAttribut.wert xml_buffer, hatGenerAttribut{}.XP_URLAttribut.name xml_buffer, hatGenerAttribut{}.XP_URLAttribut.wert xml_buffer, hatGenerAttribut{}.XP_GenerAttribut.name xml_buffer, hoehenangabe{}.XP_Hoehenangabe.abweichenderHoehenbezug xml_buffer, hoehenangabe{}.XP_Hoehenangabe.hoehenbezug xml_char(4), hoehenangabe{}.XP_Hoehenangabe.abweichenderBezugspunkt xml_buffer, hoehenangabe{}.XP_Hoehenangabe.bezugspunkt xml_char(4), hoehenangabe{}.XP_Hoehenangabe.hMin xml_real64, hoehenangabe{}.XP_Hoehenangabe.hMin.uom xml_buffer, hoehenangabe{}.XP_Hoehenangabe.hMax xml_real64, hoehenangabe{}.XP_Hoehenangabe.hMax.uom xml_buffer, hoehenangabe{}.XP_Hoehenangabe.hZwingend xml_real64, hoehenangabe{}.XP_Hoehenangabe.hZwingend.uom xml_buffer, hoehenangabe{}.XP_Hoehenangabe.h xml_real64,
      hoehenangabe{}.XP_Hoehenangabe.h.uom xml_buffer, hoehenangabe{}.XP_Hoehenangabe._GenericApplicationPropertyOfXP_Hoehenangabe{} xml_xml, externeReferenz{}.XP_SpezExterneReferenz.georefURL xml_buffer, externeReferenz{}.XP_SpezExterneReferenz.georefMimeType xml_buffer, externeReferenz{}.XP_SpezExterneReferenz.georefMimeType.codeSpace xml_buffer, externeReferenz{}.XP_SpezExterneReferenz.art xml_char(18), externeReferenz{}.XP_SpezExterneReferenz.informationssystemURL xml_buffer, externeReferenz{}.XP_SpezExterneReferenz.referenzName xml_buffer, externeReferenz{}.XP_SpezExterneReferenz.referenzURL xml_buffer, externeReferenz{}.XP_SpezExterneReferenz.referenzMimeType xml_buffer, externeReferenz{}.XP_SpezExterneReferenz.referenzMimeType.codeSpace xml_buffer, externeReferenz{}.XP_SpezExterneReferenz.beschreibung xml_buffer, externeReferenz{}.XP_SpezExterneReferenz.datum xml_date, externeReferenz{}.XP_SpezExterneReferenz._GenericApplicationPropertyOfXP_ExterneReferenz{} xml_xml, externeReferenz{}.XP_SpezExterneReferenz.typ xml_char(4), externeReferenz{}.XP_SpezExterneReferenz._GenericApplicationPropertyOfXP_SpezExterneReferenz{} xml_xml, gehoertZuBereich.nilReason xml_buffer, gehoertZuBereich.gml_remoteSchema xml_buffer, gehoertZuBereich.xlink_href xml_buffer, gehoertZuBereich.xlink_role xml_buffer, gehoertZuBereich.xlink_title xml_buffer, wirdDargestelltDurch{}.nilReason xml_buffer, wirdDargestelltDurch{}.gml_remoteSchema xml_buffer, wirdDargestelltDurch{}.xlink_href xml_buffer, wirdDargestelltDurch{}.xlink_role xml_buffer, wirdDargestelltDurch{}.xlink_title xml_buffer, refBegruendungInhalt{}.nilReason xml_buffer, refBegruendungInhalt{}.gml_remoteSchema xml_buffer, refBegruendungInhalt{}.xlink_href xml_buffer, refBegruendungInhalt{}.xlink_role xml_buffer,
      refBegruendungInhalt{}.xlink_title xml_buffer, startBedingung.XP_WirksamkeitBedingung.bedingung xml_buffer, startBedingung.XP_WirksamkeitBedingung.datumAbsolut xml_date, startBedingung.XP_WirksamkeitBedingung.datumRelativ xml_buffer, startBedingung.XP_WirksamkeitBedingung._GenericApplicationPropertyOfXP_WirksamkeitBedingung{} xml_xml, endeBedingung.XP_WirksamkeitBedingung.bedingung xml_buffer, endeBedingung.XP_WirksamkeitBedingung.datumAbsolut xml_date, endeBedingung.XP_WirksamkeitBedingung.datumRelativ xml_buffer, endeBedingung.XP_WirksamkeitBedingung._GenericApplicationPropertyOfXP_WirksamkeitBedingung{} xml_xml, aufschrift xml_buffer, _GenericApplicationPropertyOfXP_Objekt{} xml_xml, rechtscharakter xml_char(4), refTextInhalt{}.nilReason xml_buffer, refTextInhalt{}.gml_remoteSchema xml_buffer, refTextInhalt{}.xlink_href xml_buffer, refTextInhalt{}.xlink_role xml_buffer, refTextInhalt{}.xlink_title xml_buffer, wirdAusgeglichenDurchFlaeche{}.nilReason xml_buffer, wirdAusgeglichenDurchFlaeche{}.gml_remoteSchema xml_buffer, wirdAusgeglichenDurchFlaeche{}.xlink_href xml_buffer, wirdAusgeglichenDurchFlaeche{}.xlink_role xml_buffer, wirdAusgeglichenDurchFlaeche{}.xlink_title xml_buffer, wirdAusgeglichenDurchABE{}.nilReason xml_buffer, wirdAusgeglichenDurchABE{}.gml_remoteSchema xml_buffer, wirdAusgeglichenDurchABE{}.xlink_href xml_buffer, wirdAusgeglichenDurchABE{}.xlink_role xml_buffer, wirdAusgeglichenDurchABE{}.xlink_title xml_buffer, wirdAusgeglichenDurchSPEMassnahme{}.nilReason xml_buffer, wirdAusgeglichenDurchSPEMassnahme{}.gml_remoteSchema xml_buffer, wirdAusgeglichenDurchSPEMassnahme{}.xlink_href xml_buffer,
      wirdAusgeglichenDurchSPEMassnahme{}.xlink_role xml_buffer, wirdAusgeglichenDurchSPEMassnahme{}.xlink_title xml_buffer, wirdAusgeglichenDurchSPEFlaeche{}.nilReason xml_buffer, wirdAusgeglichenDurchSPEFlaeche{}.gml_remoteSchema xml_buffer, wirdAusgeglichenDurchSPEFlaeche{}.xlink_href xml_buffer, wirdAusgeglichenDurchSPEFlaeche{}.xlink_role xml_buffer, wirdAusgeglichenDurchSPEFlaeche{}.xlink_title xml_buffer, wirdAusgeglichenDurchMassnahme{}.nilReason xml_buffer, wirdAusgeglichenDurchMassnahme{}.gml_remoteSchema xml_buffer, wirdAusgeglichenDurchMassnahme{}.xlink_href xml_buffer, wirdAusgeglichenDurchMassnahme{}.xlink_role xml_buffer, wirdAusgeglichenDurchMassnahme{}.xlink_title xml_buffer, _GenericApplicationPropertyOfBP_Objekt{} xml_xml, position xml_geometry, flaechenschluss xml_boolean, _GenericApplicationPropertyOfBP_Flaechenobjekt{} xml_xml, _GenericApplicationPropertyOfBP_Flaechenschlussobjekt{} xml_xml, dachgestaltung{}.BP_Dachgestaltung.DNmin xml_real64, dachgestaltung{}.BP_Dachgestaltung.DNmin.uom xml_buffer, dachgestaltung{}.BP_Dachgestaltung.DNmax xml_real64, dachgestaltung{}.BP_Dachgestaltung.DNmax.uom xml_buffer, dachgestaltung{}.BP_Dachgestaltung.DN xml_real64, dachgestaltung{}.BP_Dachgestaltung.DN.uom xml_buffer, dachgestaltung{}.BP_Dachgestaltung.DNzwingend xml_real64, dachgestaltung{}.BP_Dachgestaltung.DNzwingend.uom xml_buffer, dachgestaltung{}.BP_Dachgestaltung.dachform xml_char(4), dachgestaltung{}.BP_Dachgestaltung.detaillierteDachform xml_buffer, dachgestaltung{}.BP_Dachgestaltung.detaillierteDachform.codeSpace xml_buffer, dachgestaltung{}.BP_Dachgestaltung._GenericApplicationPropertyOfBP_Dachgestaltung{} xml_xml, DNmin xml_real64,
      DNmin.uom xml_buffer, DNmax xml_real64, DNmax.uom xml_buffer, DN xml_real64, DN.uom xml_buffer, DNZwingend xml_real64, DNZwingend.uom xml_buffer, FR xml_real64, FR.uom xml_buffer, dachform{} xml_char(4), detaillierteDachform{} xml_buffer, detaillierteDachform{}.codeSpace xml_buffer, abweichungText{}.nilReason xml_buffer, abweichungText{}.gml_remoteSchema xml_buffer, abweichungText{}.xlink_href xml_buffer, abweichungText{}.xlink_role xml_buffer, abweichungText{}.xlink_title xml_buffer, MaxZahlWohnungen xml_int32, Fmin xml_real64, Fmin.uom xml_buffer, Fmax xml_real64, Fmax.uom xml_buffer, Bmin xml_real64, Bmin.uom xml_buffer, Bmax xml_real64, Bmax.uom xml_buffer, Tmin xml_real64, Tmin.uom xml_buffer, Tmax xml_real64, Tmax.uom xml_buffer,
      GFZmin xml_real64, GFZmax xml_real64, GFZ xml_real64, GFZ_Ausn xml_real64, GFmin xml_real64, GFmin.uom xml_buffer, GFmax xml_real64, GFmax.uom xml_buffer, GF xml_real64, GF.uom xml_buffer, GF_Ausn xml_real64, GF_Ausn.uom xml_buffer, BMZ xml_real64, BMZ_Ausn xml_real64, BM xml_real64, BM.uom xml_buffer, BM_Ausn xml_real64, BM_Ausn.uom xml_buffer, GRZmin xml_real64, GRZmax xml_real64, GRZ xml_real64, GRZ_Ausn xml_real64, GRmin xml_real64, GRmin.uom xml_buffer, GRmax xml_real64, GRmax.uom xml_buffer, GR xml_real64, GR.uom xml_buffer, GR_Ausn xml_real64, GR_Ausn.uom xml_buffer,
      Zmin xml_int32, Zmax xml_int32, Zzwingend xml_int32, Z xml_int32, Z_Ausn xml_int32, Z_Staffel xml_int32, Z_Dach xml_int32, ZUmin xml_int32, ZUmax xml_int32, ZUzwingend xml_int32, ZU xml_int32, ZU_Ausn xml_int32, wohnnutzungEGStrasse xml_char(4), ZWohn xml_int32, GFAntWohnen xml_real64, GFAntWohnen.uom xml_buffer, GFWohnen xml_real64, GFWohnen.uom xml_buffer, GFAntGewerbe xml_real64, GFAntGewerbe.uom xml_buffer, GFGewerbe xml_real64, GFGewerbe.uom xml_buffer, allgArtDerBaulNutzung xml_char(4), besondereArtDerBaulNutzung xml_char(4), sondernutzung xml_char(5), detaillierteArtDerBaulNutzung xml_buffer, detaillierteArtDerBaulNutzung.codeSpace xml_buffer, nutzungText xml_buffer, abweichungBauNVO xml_char(4), bauweise xml_char(4),
      abweichendeBauweise xml_buffer, abweichendeBauweise.codeSpace xml_buffer, vertikaleDifferenzierung xml_boolean, bebauungsArt xml_char(4), bebauungVordereGrenze xml_char(4), bebauungRueckwaertigeGrenze xml_char(4), bebauungSeitlicheGrenze xml_char(4), refGebaeudequerschnitt{}.XP_SpezExterneReferenz.georefURL xml_buffer, refGebaeudequerschnitt{}.XP_SpezExterneReferenz.georefMimeType xml_buffer, refGebaeudequerschnitt{}.XP_SpezExterneReferenz.georefMimeType.codeSpace xml_buffer, refGebaeudequerschnitt{}.XP_SpezExterneReferenz.art xml_char(18), refGebaeudequerschnitt{}.XP_SpezExterneReferenz.informationssystemURL xml_buffer, refGebaeudequerschnitt{}.XP_SpezExterneReferenz.referenzName xml_buffer, refGebaeudequerschnitt{}.XP_SpezExterneReferenz.referenzURL xml_buffer, refGebaeudequerschnitt{}.XP_SpezExterneReferenz.referenzMimeType xml_buffer, refGebaeudequerschnitt{}.XP_SpezExterneReferenz.referenzMimeType.codeSpace xml_buffer, refGebaeudequerschnitt{}.XP_SpezExterneReferenz.beschreibung xml_buffer, refGebaeudequerschnitt{}.XP_SpezExterneReferenz.datum xml_date, refGebaeudequerschnitt{}.XP_SpezExterneReferenz._GenericApplicationPropertyOfXP_ExterneReferenz{} xml_xml, refGebaeudequerschnitt{}.XP_SpezExterneReferenz.typ xml_char(4), refGebaeudequerschnitt{}.XP_SpezExterneReferenz._GenericApplicationPropertyOfXP_SpezExterneReferenz{} xml_xml, refGebaeudequerschnitt{}.XP_ExterneReferenz.georefURL xml_buffer, refGebaeudequerschnitt{}.XP_ExterneReferenz.georefMimeType xml_buffer, refGebaeudequerschnitt{}.XP_ExterneReferenz.georefMimeType.codeSpace xml_buffer, refGebaeudequerschnitt{}.XP_ExterneReferenz.art xml_char(18), refGebaeudequerschnitt{}.XP_ExterneReferenz.informationssystemURL xml_buffer, refGebaeudequerschnitt{}.XP_ExterneReferenz.referenzName xml_buffer, refGebaeudequerschnitt{}.XP_ExterneReferenz.referenzURL xml_buffer, refGebaeudequerschnitt{}.XP_ExterneReferenz.referenzMimeType xml_buffer, refGebaeudequerschnitt{}.XP_ExterneReferenz.referenzMimeType.codeSpace xml_buffer,
      refGebaeudequerschnitt{}.XP_ExterneReferenz.beschreibung xml_buffer, refGebaeudequerschnitt{}.XP_ExterneReferenz.datum xml_date, refGebaeudequerschnitt{}.XP_ExterneReferenz._GenericApplicationPropertyOfXP_ExterneReferenz{} xml_xml, zugunstenVon xml_buffer, _GenericApplicationPropertyOfBP_BaugebietsTeilFlaeche{} xml_xml
    -> AttributeValueMapper_GRZ

Bookmark: Attributmapping der GRZ, GFZ & BMZ
AttributeValueMapper_GRZ
    LUT = 1000,0.2,1100,0.4,1200,0.4,1300,0.6,1400,0.6,1500,0.6,1550,0.8,1600,1.0,1700,0.8,1800,0.8,2000,0.8,2100,0.8,3000,0.2,4000,0.8,9999,0.8
    MAPPING_DIRECTION = FORWARD
    SRC = besondereArtDerBaulNutzung
    VAL_ATTR = GRZ_Orientierungswert
    -> AttributeValueMapper_GFZ
AttributeValueMapper_GFZ
    LUT = 1000,0.4,1100,1.2,1200,1.2,1300,1.6,1400,1.2,1500,1.2,1550,3.0,1600,3.0,1700,2.4,1800,2.4,2000,2.4,2100,2.4,3000,0.2,4000,2.4,9999,2.4
    MAPPING_DIRECTION = FORWARD
    SRC = besondereArtDerBaulNutzung
    VAL_ATTR = GFZ_Orientierungswert
    -> AttributeValueMapper_BMZ
AttributeValueMapper_BMZ
    LUT = 1700,10.0
    MAPPING_DIRECTION = FORWARD
    SRC = besondereArtDerBaulNutzung
    VAL_ATTR = BMZ_Orientierungswert
    -> AreaOnAreaOverlayer_2 [AREA]

Bookmark: XPlan Theoretisches Potential Brechnung - Höhe | Volume | Grundfläche | Geschossfläche
AreaOnAreaOverlayer_2
    ACCUM_ATTRS_NAME = Merge Incoming Attributes
    CLEANING_TOLERANCE = Automatic
    CONNECT_Z_MODE = First Wins
    DEAGGREGATE_INPUT = Yes
    OVC_ATTR = _overlaps
    AREA -> Tester_3
Tester_3
    BOOL_OP = OR
    TEST_CLAUSE = TEST @Value(_overlaps) = 1
    TEST_MODE = TEST
    FAILED -> AttributeCreator
AttributeCreator
    ATTR_TABLE = SET_TO max_storeys = FME_CONDITIONAL:DEFAULT_VALUE'_FME_NO_OP_'BOOL_OP;OR;COMPOSITE_TEST;1;TEST Z ATTRIBUTE_HAS_A_VALUE _FME_BLANK_STRING_'@Value(Z)'BOOL_OP;OR;COMPOSITE_TEST;1;TEST Zzwingend ATTRIBUTE_HAS_A_VALUE _FME_BLANK_STRING_'@Value(Zzwingend)'BOOL_OP;OR;COMPOSITE_TEST;1;TEST hoehenangabe{0}.XP_Hoehenangabe.h ATTRIBUTE_HAS_A_VALUE _FME_BLANK_STRING_'@Evaluate(@floor(@Value(hoehenangabe{0}.XP_Hoehenangabe.h)/$(HEIGHT_XPlan),0))'FME_NUM_CONDITIONS4___
    -> Snapper
ExpressionEvaluator_9
    ACTION = Create New Attribute
    EXPRESSION = @Value(Calc_GeschossFlaechenZahl)/@Value(max_storeys)
    VAL_ATTR = Calc_GrundFlaechenZahl
    -> ExpressionEvaluator_8
ExpressionEvaluator_8
    ACTION = Create New Attribute
    EXPRESSION = @Value(Calc_GeschossFlaechenZahl)*$(HEIGHT_XPlan)
    VAL_ATTR = Max_Volume_km
    -> ExpressionEvaluator_10
ExpressionEvaluator_10
    ACTION = Create New Attribute
    EXPRESSION = @Value(max_storeys)*$(HEIGHT_XPlan)
    VAL_ATTR = Calc_Max_Height_from_Storeys
    -> Tester_7
Tester_7
    BOOL_OP = COMPOSITE
    COMPOSITE_TEST = 1 AND 2
    TEST_CLAUSE:
      TEST @Value(Max_BauMassenZahl) <= @Value(Max_Volume_km)
      TEST Max_BauMassenZahl NOT_ATTRIBUTE_VALUE_NULL ""
    TEST_MODE = TEST
    FAILED -> 3DForcer_5
    FAILED -> Aggregator

Bookmark: Flurstück & Reprojetion in UTM 32N
Flurstueck (reader GEOJSON_1)
    attributes: gml_parent_property string, gml_id string, oid string, aktualit string, idflurst string, flaeche int, flstkennz string, land string, landschl string, gemarkung string, gemaschl string, flurschl string, flstnrzae string, regbezirk string, regbezschl string, kreis string, kreisschl string, gemeinde string, gmdschl string, lagebeztxt string, tntxt string
    -> Reprojector
Reprojector
    DEST = EPSG:25832
    INTERPOLATION_TYPE_NAME = Nearest Neighbor
    RASTER_CELL_SIZE = Preserve Cells
    RASTER_TOLERANCE = 0.0
    SOURCE = EPSG:4326
    REPROJECTED -> Snapper

Bookmark: Geometrische Operation
Snapper
    CLEANING_TOLERANCE = Automatic
    SNAPTYPE = ALL
    TOLERANCE = 0.1
    SNAPPED -> AreaOnAreaOverlayer [AREA]
    UNTOUCHED -> AreaOnAreaOverlayer [AREA]
AreaOnAreaOverlayer
    ACCUM_ATTRS_NAME = Merge Incoming Attributes
    CLEANING_TOLERANCE = Automatic
    CONNECT_Z_MODE = First Wins
    DEAGGREGATE_INPUT = Yes
    OVC_ATTR = _overlaps
    AREA -> Tester

Bookmark: Geometrische Tests und Berechnung von Arealen und Attributen
Tester
    BOOL_OP = OR
    TEST_CLAUSE:
      TEST @Value(_overlaps) = 1
      TEST tntxt ATTRIBUTE_IS_MISSING ""
    TEST_MODE = TEST
    FAILED -> AreaCalculator_3
AreaCalculator_3
    AREA_ATTR = _area
    AREA_TYPE = Plane Area
    MULT = 1
    -> Tester_2
Tester_2
    BOOL_OP = OR
    TEST_CLAUSE = TEST @Value(_area) > $(MINAREA)
    TEST_MODE = TEST
    PASSED -> AttributeCreator_2
AttributeCreator_2
    ATTR_TABLE:
      SET_TO GFZ_aktuell = FME_CONDITIONAL:DEFAULT_VALUE'_FME_NO_OP_'BOOL_OP;OR;COMPOSITE_TEST;1;TEST GFZ ATTRIBUTE_HAS_A_VALUE _FME_BLANK_STRING_'@Value(GFZ)'BOOL_OP;OR;COMPOSITE_TEST;1;TEST GFZ_Orientierungswert ATTRIBUTE_HAS_A_VALUE _FME_BLANK_STRING_'@Value(GFZ_Orientierungswert)'FME_NUM_CONDITIONS3___
      SET_TO GRZ_aktuell = FME_CONDITIONAL:DEFAULT_VALUE'_FME_NO_OP_'BOOL_OP;OR;COMPOSITE_TEST;1;TEST GRZ ATTRIBUTE_HAS_A_VALUE _FME_BLANK_STRING_'@Value(GRZ)'BOOL_OP;OR;COMPOSITE_TEST;1;TEST GRZ_Orientierungswert ATTRIBUTE_HAS_A_VALUE _FME_BLANK_STRING_'@Value(GRZ_Orientierungswert)'FME_NUM_CONDITIONS3___
    -> ExpressionEvaluator_3

Bookmark: Berechnung von Maximalwerten basierend auf GRZ, GFZ & BMZ
ExpressionEvaluator_3
    ACTION = Create New Attribute
    EXPRESSION = @Value(flaeche)*@Value(GFZ_aktuell)
    VAL_ATTR = Max_GeschossFlaechenZahl
    -> ExpressionEvaluator_4
ExpressionEvaluator_4
    ACTION = Create New Attribute
    EXPRESSION = @Value(flaeche)*@Value(GRZ_aktuell)
    VAL_ATTR = Max_GrundFlaechenZahl
    -> ExpressionEvaluator_12
ExpressionEvaluator_12
    ACTION = Create New Attribute
    EXPRESSION = @Value(flaeche)*@Value(BMZ_Orientierungswert)
    VAL_ATTR = Max_BauMassenZahl
    -> ExpressionEvaluator_5
ExpressionEvaluator_5
    ACTION = Create New Attribute
    EXPRESSION = @Value(Max_GeschossFlaechenZahl)/@Value(max_storeys)
    VAL_ATTR = optimal_GrundFlaechenZahl
    -> Tester_4

Bookmark: Prüfung gegen Maximalwerte der Grundflächenzahl und der Geschossflächenzahl
Tester_4
    BOOL_OP = COMPOSITE
    COMPOSITE_TEST = 1 AND 2
    TEST_CLAUSE:
      TEST @Value(optimal_GrundFlaechenZahl) <= @Value(Max_GrundFlaechenZahl)
      TEST @Value(optimal_GrundFlaechenZahl) <= @Value(_area)
    TEST_MODE = TEST
    PASSED -> Junction_2
    FAILED -> Tester_5
Tester_5
    BOOL_OP = OR
    TEST_CLAUSE = TEST @Value(Max_GrundFlaechenZahl) > @Value(_area)
    TEST_MODE = TEST
    PASSED -> Junction
    FAILED -> Junction_3
Note: Areal limitiert
Junction
    -> ExpressionEvaluator_7
ExpressionEvaluator_7
    ACTION = Create New Attribute
    EXPRESSION = @Value(_area)*@Value(max_storeys)
    VAL_ATTR = Calc_GeschossFlaechenZahl
    -> ExpressionEvaluator_9
Note: GRZ limitiert
Junction_3
    -> ExpressionEvaluator_6
ExpressionEvaluator_6
    ACTION = Create New Attribute
    EXPRESSION = @Value(Max_GrundFlaechenZahl)*@Value(max_storeys)
    VAL_ATTR = Calc_GeschossFlaechenZahl
    -> ExpressionEvaluator_9
Note: Optimale Ausnutzung
Junction_2
    -> AttributeCreator_3
AttributeCreator_3
    ATTR_TABLE = SET_TO Calc_GeschossFlaechenZahl = @Value(Max_GeschossFlaechenZahl)
    -> ExpressionEvaluator_9

Bookmark: 3D Repräsentation des Potentialvolumens
3DForcer_5
    KEEPZVAL = No
    ZVALATTR = 0
    -> Counter_2
Counter_2
    CNT_ATTR = _count
    DOMAIN = counter
    SCOPE = Global
    START = 0
    -> Extruder_6
Extruder_6
    DIRECTION = Auto
    DISTANCE = @Value(max_storeys)*$(HEIGHT_XPlan)
    EXTRUDED -> Aggregator_3
Aggregator_3
    ACCUM_ATTRS_NAME = Drop Incoming Attributes
    AGGREGATE_TYPE = Homogeneous Collection (If Possible)
    GROUP_BY = oid
    MODE = Geometry - Assemble One Level
    SEP = ,
    SUM = Max_Volume_km
    AGGREGATE -> FeatureMerger [REQUESTOR]

Bookmark: Vergleich der Potentiale
Aggregator
    ACCUM_ATTRS_NAME = Drop Incoming Attributes
    AGGREGATE_TYPE = Homogeneous Collection (If Possible)
    GROUP_BY = oid besondereArtDerBaulNutzung
    MODE = Geometry - Assemble One Level
    SEP = ,
    SUM = Max_Volume_km
    AGGREGATE -> PointOnAreaOverlayer [AREA]
PointOnAreaOverlayer
    ATTR_ACCUM_MODE = Merge Incoming
    ATTR_CONFLICT_RES = Use Original
    CANDIDATE_LIST_ATTRS_TO_INCLUDE = gml_id gml_parent_id volume_geometry volume_measured_height volume_storeys
    CANDIDATE_LIST_ATTRS_TO_INCLUDE_MODE = Selected Attributes
    CANDIDATE_LIST_NAME = CityGML_Volumes
    DEAGGREGATE_INPUT = Yes
    OV_ATTR = _overlaps
    POLYS_FIRST = NO
    AREA -> ListExploder
ListExploder
    ATTR_ACCUM_MODE = Merge List Attributes
    ATTR_CONFLICT_RES = Use List Attribute Values
    INDEX_ATTR = _element_index
    LIST_ATTR = CityGML_Volumes{}
    ELEMENTS -> Dissolver_2
Dissolver_2
    ACCUM_INPUT_ATTRS = Use Attributes From One Feature
    CLEANING_TOLERANCE = Automatic
    CONNECT_Z_MODE = First Wins
    DEAGGREGATE_INPUT = Yes
    GROUP_BY = oid Max_Volume_km
    SUM = volume_geometry volume_measured_height volume_storeys
    AREA -> Aggregator_2
Aggregator_2
    ACCUM_ATTRS_NAME = Drop Incoming Attributes
    AGGREGATE_TYPE = Homogeneous Collection (If Possible)
    GROUP_BY = oid Max_Volume_km besondereArtDerBaulNutzung
    LIST_ATTRS_TO_INCLUDE = volume_geometry volume_measured_height volume_storeys
    LIST_NAME = volumes
    MODE = Geometry - Assemble One Level
    SEP = ,
    SUM = volume_geometry volume_measured_height volume_storeys
    AGGREGATE -> Potentialtest
    AGGREGATE -> AttributeValueMapper_GFZ_2
Potentialtest: Tester
    BOOL_OP = COMPOSITE
    COMPOSITE_TEST = 1 AND 2 AND 3
    TEST_CLAUSE:
      TEST @Value(volume_geometry) <= @Value(Max_Volume_km)
      TEST @Value(volume_measured_height) <= @Value(Max_Volume_km)
      TEST @Value(volume_storeys) <= @Value(Max_Volume_km)
    TEST_MODE = TEST
    PASSED -> AppearanceStyler
    FAILED -> AppearanceStyler_2
AppearanceStyler
    ALPHA = 0.7
    APPEARANCE_NAME = Potential_Color
    DIFFUSE_COLOR = 0,1,0
    TEXTURE_CENTER_U = 0.0
    TEXTURE_CENTER_V = 0.0
    TEXTURE_ROTATION_ANGLE = 0.0
    TEXTURE_U_OFFSET = 0.0
    TEXTURE_U_SCALING_FACTOR = 1.0
    TEXTURE_U_SHEARING_FACTOR = 0.0
    TEXTURE_V_OFFSET = 0.0
    TEXTURE_V_SCALING_FACTOR = 1.0
    TEXTURE_V_SHEARING_FACTOR = 0.0
    TEXTURE_WRAP_DISPLAY = Repeat in U and V
    -> FeatureMerger [SUPPLIER]
AppearanceStyler_2 [off]
    ALPHA = 0.7
    APPEARANCE_NAME = OhnePotential_Color
    DIFFUSE_COLOR = 1,1,0
    TEXTURE_CENTER_U = 0.0
    TEXTURE_CENTER_V = 0.0
    TEXTURE_ROTATION_ANGLE = 0.0
    TEXTURE_U_OFFSET = 0.0
    TEXTURE_U_SCALING_FACTOR = 1.0
    TEXTURE_U_SHEARING_FACTOR = 0.0
    TEXTURE_V_OFFSET = 0.0
    TEXTURE_V_SCALING_FACTOR = 1.0
    TEXTURE_V_SHEARING_FACTOR = 0.0
    TEXTURE_WRAP_DISPLAY = Repeat in U and V
    -> FeatureMerger [SUPPLIER]
FeatureMerger
    ATTR_ACCUM_MODE = Merge Supplier
    ATTR_CONFLICT_RES = Use Requestor
    IGNORE_NULLS = No
    JOIN_KEYS = @Value(oid) @Value(oid) AUTO
    MERGE_TYPE = Attributes Only
    PROCESS_DUPS = NO
    REJECT_NULL_MISSING_KEYS = No
    SUPPLIERS_FIRST = No
    MERGED -> AppearanceSetter [GEOMETRY]
    MERGED -> GeometryRemover
GeometryRemover
    -> AppearanceSetter [APPEARANCE]
AppearanceSetter
    DEF_STORAGE = Create New Definitions
    GQUERY:
      for $geom in //geometry
      where $geom/count(parent::geometry) = 0
      return number($geom/@fme_id)
    GROUP_BY = oid
    SET_ON_SIDE = Front and Back Sides
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> Aggregator_4
    -> XPlanPotential (writer GLTF_1)
AttributeValueMapper_GFZ_2
    LUT = 1000,Kleinsiedlungsgebiet,1100,ReinesWohngebiet,1200,AllgWohngebiet,1300,BesonderesWohngebiet,1400,Dorfgebiet,1500,Mischgebiet,1550,UrbanesGebiet,1600,Kerngebiet,1700,Gewerbegebiet,1800,Industriegebiet,2000,SondergebietErholung,2100,SondergebietSonst,3000,Wochenendhausgebiet,4000,Sondergebiet,9999,SonstigesGebiet
    MAPPING_DIRECTION = FORWARD
    SRC = besondereArtDerBaulNutzung
    VAL_ATTR = Baugebiete
    -> AttributeManager
AttributeManager
    ATTR_TABLE:
      REMOVE besondereArtDerBaulNutzung
      RENAME_SET_VALUE oid > Flurstück ID
      RENAME_SET_VALUE Baugebiete > Baugebietstyp
      RENAME_SET_VALUE Max_Volume_km > Maximales potentielles Volumen (m³)
      RENAME_SET_VALUE volume_geometry > CityGML Volumen aus Geometry (m³)
      RENAME_SET_VALUE volume_storeys > CityGML Volumen aus Geschossen (m³)
      RENAME_SET_VALUE volume_measured_height > CityGML Volumen aus Höhenattribut (m³)
      REMOVE volumes{}.volume_geometry
      REMOVE volumes{}.volume_storeys
      REMOVE volumes{}.volume_measured_height
    -> Potential_analysis_FME (writer XLSXW_1)

Bookmark: CityGML Input Feature
Building (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, DatenquelleBodenhoehe xml_buffer, DatenquelleDachhoehe xml_buffer, DatenquelleLage xml_buffer, Gemeindeschluessel xml_buffer, Geometrietyp2DReferenz xml_buffer, Grundrissaktualitaet xml_buffer
    -> VolumeCalculator_3
BuildingPart (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, DatenquelleBodenhoehe xml_buffer, DatenquelleDachhoehe xml_buffer, DatenquelleLage xml_buffer, Grundrissaktualitaet xml_buffer
    -> VolumeCalculator_3

Bookmark: CityGML Real Volumen Berechnung
VolumeCalculator_3
    MULT = 1
    SET_TRAIT = No
    VOLUME_ATTR = volume_geometry
    -> SurfaceFootprintReplacer_2

Bookmark: Volumenberechnung basierend auf Geschossanzahl
SurfaceFootprintReplacer_2
    OFFSET_Z = 0
    SHADOW_MODE = Overhead Shadow
    FOOTPRINT -> Extruder_2
Extruder_2
    DIRECTION = Auto
    DISTANCE = $(HEIGHT_CityGML)*@Value(citygml_storeys_above_ground)
    EXTRUDED -> VolumeCalculator_5
    EXTRUDED -> Aggregator_4
    EXTRUDED -> CityGMLBuildingByStoreys (writer GLTF_1)
VolumeCalculator_5
    MULT = 1
    SET_TRAIT = No
    VOLUME_ATTR = volume_storeys
    -> SurfaceFootprintReplacer_3

Bookmark: Volumenberechnung basierend auf Höhenattribut
SurfaceFootprintReplacer_3
    OFFSET_Z = 0
    SHADOW_MODE = Overhead Shadow
    FOOTPRINT -> Extruder_4
Extruder_4
    DIRECTION = Auto
    DISTANCE = @Value(citygml_measured_height)
    EXTRUDED -> VolumeCalculator_6
VolumeCalculator_6
    MULT = 1
    SET_TRAIT = No
    VOLUME_ATTR = volume_measured_height
    -> SurfaceFootprintReplacer_5

Bookmark: Geometrische Operationen
SurfaceFootprintReplacer_5
    OFFSET_Z = 0
    SHADOW_MODE = Overhead Shadow
    FOOTPRINT -> CenterPointReplacer
CenterPointReplacer
    POINTTYPE = INSIDE
    POINT -> PointOnAreaOverlayer [POINT]

Bookmark: Export GLTF Daten & Excel Potential Liste
CityGML_XPlanVergleich (writer GLTF_1)
XPlanPotential (writer GLTF_1)
Potential_analysis_FME (writer XLSXW_1)
    attributes: Flurstück ID string(20), Baugebietstyp string(20), Maximales potentielles Volumen (m³) number(20), CityGML Volumen aus Geometry (m³) number(20), CityGML Volumen aus Geschossen (m³) number(20), CityGML Volumen aus Höhenattribut (m³) number(20)
CityGMLBuildingByStoreys (writer GLTF_1)
